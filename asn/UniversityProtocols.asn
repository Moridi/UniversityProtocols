UniversityProtocols DEFINITIONS ::= BEGIN

-- ACM PROTOCOL

Acmp ::= SEQUENCE 
{
	budget INTEGER(0..65535),
	consumed INTEGER(0..65535)
}

-- IEEE PROTOCOL

Ieeep ::= SEQUENCE 
{
	budget INTEGER(0..255),
	consumed INTEGER(0..255)
}

END
